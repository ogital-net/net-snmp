-- Minimal NATV2-MIB definition for snmpwalk display.
-- Based on RFC 7659 (Definitions of Managed Objects for NATs).
-- Only the objects implemented by VPP integration are included here.

NATV2-MIB DEFINITIONS ::= BEGIN

IMPORTS
    MODULE-IDENTITY, OBJECT-TYPE, Counter64, Gauge32, Integer32,
    mib-2
        FROM SNMPv2-SMI
    MODULE-COMPLIANCE, OBJECT-GROUP
        FROM SNMPv2-CONF;

natv2MIB MODULE-IDENTITY
    LAST-UPDATED "201510010000Z"
    ORGANIZATION "IETF BEHAVE Working Group"
    CONTACT-INFO "See RFC 7659"
    DESCRIPTION
        "MIB module for NAT version 2 (subset for VPP integration).
         See RFC 7659 for the full specification."
    REVISION "201510010000Z"
    DESCRIPTION "Initial version per RFC 7659."
    ::= { mib-2 234 }

natv2MIBObjects OBJECT IDENTIFIER ::= { natv2MIB 1 }

-- ======================================================================
-- Protocol Statistics Table
-- ======================================================================

natv2ProtocolStatsTable OBJECT-TYPE
    SYNTAX      SEQUENCE OF Natv2ProtocolStatsEntry
    MAX-ACCESS  not-accessible
    STATUS      current
    DESCRIPTION
        "Per-protocol NAT translation statistics."
    ::= { natv2MIBObjects 6 }

natv2ProtocolStatsEntry OBJECT-TYPE
    SYNTAX      Natv2ProtocolStatsEntry
    MAX-ACCESS  not-accessible
    STATUS      current
    DESCRIPTION
        "A row for a particular IP protocol."
    INDEX { natv2ProtocolStatsProtocol }
    ::= { natv2ProtocolStatsTable 1 }

Natv2ProtocolStatsEntry ::= SEQUENCE {
    natv2ProtocolStatsProtocol       Integer32,
    natv2ProtocolStatsInTranslates   Counter64,
    natv2ProtocolStatsOutTranslates  Counter64,
    natv2ProtocolStatsDiscards       Counter64
}

natv2ProtocolStatsProtocol OBJECT-TYPE
    SYNTAX      Integer32 (0..255)
    MAX-ACCESS  not-accessible
    STATUS      current
    DESCRIPTION
        "IANA protocol number (6=TCP, 17=UDP, 1=ICMP, 255=other)."
    ::= { natv2ProtocolStatsEntry 1 }

natv2ProtocolStatsInTranslates OBJECT-TYPE
    SYNTAX      Counter64
    MAX-ACCESS  read-only
    STATUS      current
    DESCRIPTION
        "Packets translated in the inside-to-outside direction."
    ::= { natv2ProtocolStatsEntry 2 }

natv2ProtocolStatsOutTranslates OBJECT-TYPE
    SYNTAX      Counter64
    MAX-ACCESS  read-only
    STATUS      current
    DESCRIPTION
        "Packets translated in the outside-to-inside direction."
    ::= { natv2ProtocolStatsEntry 3 }

natv2ProtocolStatsDiscards OBJECT-TYPE
    SYNTAX      Counter64
    MAX-ACCESS  read-only
    STATUS      current
    DESCRIPTION
        "Packets discarded due to resource constraints."
    ::= { natv2ProtocolStatsEntry 4 }

-- ======================================================================
-- Global Statistics (scalars)
-- ======================================================================

natv2GlobalStats OBJECT IDENTIFIER ::= { natv2MIBObjects 10 }

natv2GlobalActiveSessions OBJECT-TYPE
    SYNTAX      Gauge32
    MAX-ACCESS  read-only
    STATUS      current
    DESCRIPTION
        "Current number of active NAT sessions."
    ::= { natv2GlobalStats 1 }

natv2GlobalMaxSessions OBJECT-TYPE
    SYNTAX      Gauge32
    MAX-ACCESS  read-only
    STATUS      current
    DESCRIPTION
        "Maximum number of NAT sessions the device can support."
    ::= { natv2GlobalStats 2 }

natv2GlobalInTranslates OBJECT-TYPE
    SYNTAX      Counter64
    MAX-ACCESS  read-only
    STATUS      current
    DESCRIPTION
        "Total packets translated inside-to-outside across all protocols."
    ::= { natv2GlobalStats 3 }

natv2GlobalOutTranslates OBJECT-TYPE
    SYNTAX      Counter64
    MAX-ACCESS  read-only
    STATUS      current
    DESCRIPTION
        "Total packets translated outside-to-inside across all protocols."
    ::= { natv2GlobalStats 4 }

natv2GlobalDrops OBJECT-TYPE
    SYNTAX      Counter64
    MAX-ACCESS  read-only
    STATUS      current
    DESCRIPTION
        "Total packets dropped due to NAT resource constraints
         (session exhaustion, port exhaustion, etc.)."
    ::= { natv2GlobalStats 5 }

-- ======================================================================
-- Conformance
-- ======================================================================

natv2MIBConformance OBJECT IDENTIFIER ::= { natv2MIB 2 }
natv2MIBGroups      OBJECT IDENTIFIER ::= { natv2MIBConformance 1 }
natv2MIBCompliances OBJECT IDENTIFIER ::= { natv2MIBConformance 2 }

natv2StatsGroup OBJECT-GROUP
    OBJECTS {
        natv2GlobalActiveSessions,
        natv2GlobalMaxSessions,
        natv2GlobalInTranslates,
        natv2GlobalOutTranslates,
        natv2GlobalDrops,
        natv2ProtocolStatsInTranslates,
        natv2ProtocolStatsOutTranslates,
        natv2ProtocolStatsDiscards
    }
    STATUS current
    DESCRIPTION "NAT statistics objects."
    ::= { natv2MIBGroups 1 }

natv2ReadOnlyCompliance MODULE-COMPLIANCE
    STATUS current
    DESCRIPTION "Read-only compliance for NAT statistics."
    MODULE
        MANDATORY-GROUPS { natv2StatsGroup }
    ::= { natv2MIBCompliances 1 }

END
